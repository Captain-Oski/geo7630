FME workspace TP1_Popa_Diana.fmw

Parameters:
- SourceDataset_SHAPEFILE_11 = https://data.montreal.ca/dataset/2fc8a2b9-1556-410e-a118-c46e97e9f19e/resource/c08b5a11-549f-409d-9d2a-04eb3a10b66a/download/interventions-sim.zip   # Source Esri Shapefile(s)
- SourceDataset_SHAPEFILE_9 = https://data.montreal.ca/dataset/5829b5b0-ea6f-476f-be94-bc2b8797769a/resource/1171793b-3c41-4dd5-ab99-7bd294c0c9f0/download/actes-criminels.zip   # Source Esri Shapefile(s)
- SourceDataset_SHAPEFILE_8 = https://data.montreal.ca/dataset/49af1f40-6a69-494f-8fa3-b84b532a7dd6/resource/7157e8e8-8d01-4d3f-b99b-28a79db013ce/download/territoires-administratifs-casernes.zip   # Source Esri Shapefile(s)
- SourceDataset_SHAPEFILE_13 = https://data.montreal.ca/dataset/4ad6baea-4d2c-460f-a8bf-5d000db498f7/resource/43c2cccf-a439-429b-a3c8-5d4ebce53e1b/download/uniteevaluationfonciere.zip   # Source Esri Shapefile(s)
- SourceDataset_LAS_6 = http://depot.ville.montreal.qc.ca/geomatique/lidar_aerien/2015/294-5049_2015.laz   # Source ASPRS LAS File(s)
- SourceDataset_LAS = http://depot.ville.montreal.qc.ca/geomatique/lidar_aerien/2015/294-5048_2015.laz   # Source ASPRS LAS File(s)
- DestDataset_POSTGIS = GEO7630   # Connection
- SourceDataset_SHAPEFILE = fme://google-drive/building_2021_p_point.zip?id=1-I7EjxBFaZ3tCpmzakczP5mXwHDgcGYV&module=googledrive&webservice=Google%20Drive&connection=admin%20Google%20Drive   # Source Esri Shapefile(s)
- SourceDataset_PNGRASTER_3 = fme://google-drive/Image_MTL.png.zip?id=1I072wb2b8d6FKaz58_rFQ64_Bnwvb56X&module=googledrive&webservice=Google%20Drive&connection=admin%20Google%20Drive   # Source PNG (Portable Network Graphics) File(s)
- DestDataset_POSTGIS_5 = GEO7630   # Connection
- DestDataset_POSTGIS_7 = GEO7630   # Connection
- DestDataset_POSTGIS_6 = GEO7630   # Connection

Readers:
- SHAPEFILE_2: SHAPEFILE from $(SourceDataset_SHAPEFILE_11)
- SHAPEFILE_3: SHAPEFILE from $(SourceDataset_SHAPEFILE_9)
- SHAPEFILE_4: SHAPEFILE from $(SourceDataset_SHAPEFILE_8)
- SHAPEFILE_5: SHAPEFILE from $(SourceDataset_SHAPEFILE_13)
- LAS_1: LAS from $(SourceDataset_LAS)
- LAS_4: LAS from $(SourceDataset_LAS_6)
- SHAPEFILE_1: SHAPEFILE from $(SourceDataset_SHAPEFILE)
- PNGRASTER_2: PNGRASTER from $(SourceDataset_PNGRASTER_3)

Writers:
- POSTGIS_1: POSTGIS to $(DestDataset_POSTGIS) in EPSG:3857
- POSTGIS_2: POSTGIS to $(DestDataset_POSTGIS_5)
- POSTGIS_3: POSTGIS to $(DestDataset_POSTGIS_7)
- POSTGIS_4: POSTGIS to $(DestDataset_POSTGIS_6)

batiments_3D_RasterColor (writer POSTGIS_2)
    attributes: color_rgb varchar(200), g_type varchar(15), g_longitud varchar(50), g_latitude varchar(50), g_elevatio varchar(50), etage_hors int8, annee_construction int8, utilisation varchar(156), no_arrondissement varchar(80), _overlaps int8, _sum float8, z varchar(200)
Tendances_AC_SIM (writer POSTGIS_3)
    attributes: creation_date varchar(80), crimes_categorie varchar(80), crimes_pdq float8, sim_incident_t varchar(80), sim_description varchar(80), sim_caserne int8, sim_nombre_uni float8, nom_arrondissement varchar(80), no_caserne int4, x float8, y float8, _geometry text, _h3index numeric(20,0), point_count int8
Casernes_H3 (writer POSTGIS_4)
    attributes: creation_date varchar(80), crimes_categorie varchar(80), crimes_pdq float8, sim_incident_t varchar(80), sim_description varchar(80), sim_caserne int8, sim_nombre_uni float8, nom_arrondissement varchar(80), no_caserne int4, _x float8, _y float8, _geometry text, _h3index numeric(20,0), point_count int8

Bookmark: Extraction des couleurs du Raster
PNGRASTER (reader PNGRASTER_2)
    attributes: datatype char(255)
    -> Reprojector_2
    -> RasterBandPropertyExtractor
RasterBandPropertyExtractor
    -> ListExploder
Note: Bande alpha n'apparait pas dans le raster alors il n'est pas nécessaire de l'éliminer.
ListExploder
    ATTR_ACCUM_MODE = Merge List Attributes
    ATTR_CONFLICT_RES = Use List Attribute Values
    INDEX_ATTR = _element_index
    LIST_ATTR = _band{}
Reprojector_2
    DEST = EPSG:3857
    INTERPOLATION_TYPE_NAME = Nearest Neighbor
    RASTER_CELL_SIZE = Preserve Cells
    RASTER_TOLERANCE = 0.0
    REPROJECTED -> RasterPropertyExtractor
    REPROJECTED -> RasterResampler
RasterPropertyExtractor
    <REJECTED> -> Logger_7
Note: Pour changer la résolution (RasterResampler)
Logger_7
    LOG_FEATURE = LOG_ONLY
    MAXCOORDS = 20
    MAXFEATS = 20
    MESSAGE = Feature is:
    SEVERITY = INFO
Note: Reéchantillonnage (5m)
RasterResampler
    COLUMNS = 263
    INTERPOLATION_TYPE_NAME = Nearest Neighbor
    ROWCOL_OR_CELLSIZE = RowsColumns
    ROWS = 295
    RESAMPLED -> RasterCellCoercer
    <REJECTED> -> Logger_8
RasterCellCoercer
    CELL_GEOMETRY = Points
    EXTRACT_BAND_VALUES_AS = Attributes
    EXTRACT_NODATA = Yes
    PRESERVE_ATTRIBUTES = Yes
    -> AttributeManager_5
    <REJECTED> -> Logger_5
AttributeManager_5
    ATTR_TABLE = SET_TO color_rgb = fme_fill_color = @Evaluate(@Value(_band{0}.value)/256),@Evaluate(@Value(_band{1}.value)/256),@Evaluate(@Value(_band{2}.value)/256)
    -> ColorConverter
Note: Conversion des couleurs du Raster en couleurs FME
ColorConverter
    InputAttribute = color_rgb
    InputModel = FME
    OutputModel = FME
    -> FeatureColorSetter
FeatureColorSetter
    FILL_COLOR = @Value(_output_color)
    MODE = Fixed
    COLORED -> PointOnAreaOverlayer_3 [POINT]
    <REJECTED> -> Logger_9
Logger_9
    LOG_FEATURE = LOG_ONLY
    MAXCOORDS = 20
    MAXFEATS = 20
    MESSAGE = Feature is:
    SEVERITY = INFO
Logger_5
    LOG_FEATURE = LOG_ONLY
    MAXCOORDS = 20
    MAXFEATS = 20
    MESSAGE = Feature is:
    SEVERITY = INFO
Logger_8
    LOG_FEATURE = LOG_ONLY
    MAXCOORDS = 20
    MAXFEATS = 20
    MESSAGE = Feature is:
    SEVERITY = INFO

Bookmark: Actes criminels et interventions SIM - Reprojection (3857), reconfiguration des attributs, jointure des deux tables
actes-criminels (reader SHAPEFILE_3)
    attributes: CATEGORIE varchar(80), DATE varchar(80), QUART varchar(80), PDQ double, X double, Y double, LONGITUDE double, LATITUDE double
    -> Reprojector_3
Reprojector_3
    DEST = EPSG:3857
    INTERPOLATION_TYPE_NAME = Nearest Neighbor
    RASTER_CELL_SIZE = Preserve Cells
    RASTER_TOLERANCE = 0.0
    REPROJECTED -> Configuration_latitude_ac
Configuration_latitude_ac: SubstringExtractor
    END = 4
    RESULT_ATTR = Latitude_ac
    SRC_STRING = @Value(LATITUDE)
    START = 0
    -> Configuration_longitude_ac
Configuration_longitude_ac: SubstringExtractor
    END = 5
    RESULT_ATTR = Longitude_ac
    SRC_STRING = @Value(LONGITUDE)
    START = 0
    -> FeatureMerger [REQUESTOR]
interventions-sim (reader SHAPEFILE_2)
    attributes: INCIDENT_N number(18,0), CREATION_D varchar(80), INCIDENT_T varchar(80), DESCRIPTIO varchar(80), CASERNE number(18,0), NOM_VILLE varchar(80), NOM_ARROND varchar(80), DIVISION number(18,0), NOMBRE_UNI double, MTM8_X double, MTM8_Y double, LONGITUDE double, LATITUDE double
    -> Reprojector_4
Reprojector_4
    DEST = EPSG:3857
    INTERPOLATION_TYPE_NAME = Nearest Neighbor
    RASTER_CELL_SIZE = Preserve Cells
    RASTER_TOLERANCE = 0.0
    REPROJECTED -> Suppression_Heure
Note: Contrairement aux crimes, l'attribut (SIM) comportant la date de l'événement incluait également l'heure. Afin de pouvoir le joindre au document "Actes criminels", j'ai conservé la date seulement. / - Nouveau champ : "Date"
Suppression_Heure: SubstringExtractor
    END = 9
    RESULT_ATTR = Date
    SRC_STRING = @Value(CREATION_D)
    START = 0
    -> Configuration_latitude_SIM
Note: Reconfiguration de la précision des latitudes et longitudes à deux chiffres après la virgule. Considérant que la localisation des points est approximative afin de conserver la confidentialité des événements, il semblait logique que des points (crimes et interventions) à proximité ayant la même date soient considérés comme le même événement. Cette étape a été appliquée aux crimes et interventions SIM afin de les joindre.
Configuration_latitude_SIM: SubstringExtractor
    END = 4
    RESULT_ATTR = Latitude_SIM
    SRC_STRING = @Value(LATITUDE)
    START = 0
    -> Configuration_longitude_SIM
Configuration_longitude_SIM: SubstringExtractor
    END = 5
    RESULT_ATTR = Longitude_SIM
    SRC_STRING = @Value(LONGITUDE)
    START = 0
    -> FeatureMerger [SUPPLIER]
Note: Jointure des deux tables en fonction des dates et coordonnées X,Y qui sont les mêmes. Il n'y a pas de dédoublement de points car la géométrie a été fusionnée également.
FeatureMerger
    ATTR_ACCUM_MODE = Merge Supplier
    ATTR_CONFLICT_RES = Use Requestor
    IGNORE_NULLS = No
    JOIN_KEYS = @Value(DATE) @Value(Date) AUTO @Value(Latitude_ac) @Value(Latitude_SIM) AUTO @Value(Longitude_ac) @Value(Longitude_SIM) AUTO
    MERGE_TYPE = Attributes and Geometry
    PROCESS_DUPS = NO
    REJECT_NULL_MISSING_KEYS = No
    SUPPLIERS_FIRST = No
    MERGED -> AttributeManager_2
    <REJECTED> -> Logger_2
AttributeManager_2
    ATTR_TABLE:
      RENAME_SET_VALUE CREATION_D > creation_d
      RENAME_SET_VALUE CATEGORIE > crimes_categorie
      REMOVE DATE
      REMOVE QUART
      RENAME_SET_VALUE PDQ > crimes_pdq
      REMOVE X
      REMOVE Y
      REMOVE INCIDENT_N
      RENAME_SET_VALUE INCIDENT_T > sim_incident_t
      RENAME_SET_VALUE DESCRIPTIO > sim_description
      RENAME_SET_VALUE CASERNE > sim_caserne
      REMOVE NOM_VILLE
      REMOVE DIVISION
      RENAME_SET_VALUE NOMBRE_UNI > sim_nombre_uni
      REMOVE MTM8_X
      REMOVE MTM8_Y
      REMOVE Date
      REMOVE Latitude_SIM
      REMOVE Longitude_SIM
      RENAME_SET_VALUE NOM_ARROND > nom_arrondissement
      RENAME_SET_VALUE LONGITUDE > longitude
      RENAME_SET_VALUE LATITUDE > latitude
    USER_EXPOSED_ATTRIBUTES = Latitude,Longitude
    -> GeometryValidator
Logger_2
    LOG_FEATURE = LOG_ONLY
    MAXCOORDS = 20
    MAXFEATS = 20
    MESSAGE = Feature is:
    SEVERITY = INFO

Bookmark: Tendances obtenues et les territoires des casernes - Indexation hexagonale (H3), Jointure spatiale
Note: Validation de la géométrie afin d'assurer le bon fonctionnement de la jointure spatiale
GeometryValidator
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> PointOnAreaOverlayer [POINT]
    <REJECTED> -> GeometryValidator__Rejected_
GeometryValidator__Rejected_: Logger
    LOG_FEATURE = LOG_ONLY
    MAXCOORDS = 20
    MAXFEATS = 20
    MESSAGE = Feature is:
    SEVERITY = INFO
territoires-administratifs-casernes (reader SHAPEFILE_4)
    attributes: NOM_CAS_AD varchar(80), NO_CAS_ADM long, OBJECTID long
    -> Reprojector_6
Note: Reprojection à EPSG:4326 (lat, long) afin que l'indexation hexagonale fonctionne.
Reprojector_6
    DEST = EPSG:4326
    INTERPOLATION_TYPE_NAME = Nearest Neighbor
    RASTER_CELL_SIZE = Preserve Cells
    RASTER_TOLERANCE = 0.0
    REPROJECTED -> CoordinateExtractor
CoordinateExtractor
    IND = 0
    MODE = Specify Coordinate
    X_ATTR = _x
    Y_ATTR = _y
    -> GeometryExtractor
    <REJECTED> -> Logger_14
GeometryExtractor
    ATTR = _geometry
    KIND_LONG = FME Binary
    REMOVE_GEOMETRY = No
    -> GeometryValidator_2
    <REJECTED> -> Logger_17
GeometryValidator_2
    ISSUE_ATTR_NAME = _issues
    PRESETS = Basic Integrity
    REPAIR = Yes
    RULES = NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR
    SUMMARY = Detailed
    PASSED -> H3HexagonalIndexer
    <REJECTED> -> Logger_18
H3HexagonalIndexer
    INDEX_OPERATION = Filling Indexes
    -> Reprojector_7
    <REJECTED> -> Logger_4
Note: Reprojection à EPSG: 3857 suite à l'indexation hexagonale.
Reprojector_7
    DEST = EPSG:3857
    INTERPOLATION_TYPE_NAME = Nearest Neighbor
    RASTER_CELL_SIZE = Preserve Cells
    RASTER_TOLERANCE = 0.0
    SOURCE = EPSG:4326
    REPROJECTED -> PointOnAreaOverlayer [AREA]
Note: Jointure spatiale du résultat (tendances entres crimes et interventions SIM) et les territoires administratifs des casernes.
PointOnAreaOverlayer
    ATTR_ACCUM_MODE = Merge Incoming
    ATTR_CONFLICT_RES = Use Incoming
    DEAGGREGATE_INPUT = Yes
    OV_ATTR = point_count
    POLYS_FIRST = NO
    POINT -> AttributeManager_4
    AREA -> AttributeManager_3
    <REJECTED> -> Logger_3
Note: Nettoyage
AttributeManager_4
    ATTR_TABLE:
      RENAME_SET_VALUE creation_d > creation_date
      REMOVE Latitude
      REMOVE Longitude
      REMOVE longitude
      REMOVE latitude
      REMOVE Latitude_ac
      REMOVE Longitude_ac
      REMOVE NOM_CAS_AD
      RENAME_SET_VALUE NO_CAS_ADM > no_caserne
      REMOVE OBJECTID
      RENAME_SET_VALUE _x > x
      RENAME_SET_VALUE _y > y
    -> NullAttributeMapper
Note: Identification des valeurs nulles
NullAttributeMapper
    ATTRCHOICE = All Attributes
    NULL_TREATMENT = Null
    OTHER_VALUE = :
    SOURCE_ATTR_VAL = Null
    -> Tendances_AC_SIM (writer POSTGIS_3)
AttributeManager_3
    ATTR_TABLE:
      RENAME_SET_VALUE creation_d > creation_date
      REMOVE Latitude
      REMOVE Longitude
      REMOVE longitude
      REMOVE latitude
      REMOVE Latitude_ac
      REMOVE Longitude_ac
      REMOVE NOM_CAS_AD
      RENAME_SET_VALUE NO_CAS_ADM > no_caserne
      REMOVE OBJECTID
    -> Casernes_H3 (writer POSTGIS_4)
Logger_3
    LOG_FEATURE = LOG_ONLY
    MAXCOORDS = 20
    MAXFEATS = 20
    MESSAGE = Feature is:
    SEVERITY = INFO
Logger_4
    LOG_FEATURE = LOG_ONLY
    MAXCOORDS = 20
    MAXFEATS = 20
    MESSAGE = Feature is:
    SEVERITY = INFO
Logger_18
    LOG_FEATURE = LOG_ONLY
    MAXCOORDS = 20
    MAXFEATS = 20
    MESSAGE = Feature is:
    SEVERITY = INFO
Logger_17
    LOG_FEATURE = LOG_ONLY
    MAXCOORDS = 20
    MAXFEATS = 20
    MESSAGE = Feature is:
    SEVERITY = INFO
Logger_14
    LOG_FEATURE = LOG_ONLY
    MAXCOORDS = 20
    MAXFEATS = 20
    MESSAGE = Feature is:
    SEVERITY = INFO

Bookmark: Bâtiments (Geoindex), Unités d'évaluation foncière - Reprojection (3857), jointure spatiale, indexation hexagonale (H3)
dmti_building_2021_p_point (reader SHAPEFILE_1)
    attributes: g_objectid varchar(50), g_uid varchar(36), g_name varchar(70), g_address varchar(45), g_municipa varchar(60), g_prov varchar(2), g_post_cod varchar(7), g_phone varchar(15), g_fax varchar(11), g_toll_fre varchar(15), g_type varchar(15), g_longitud varchar(50), g_latitude varchar(50), g_elevatio varchar(50), g_accuracy varchar(50), g_acq_tech varchar(50), g_dat_acqu varchar(50), g_dat_char varchar(50)
    -> Reprojector
Reprojector
    DEST = EPSG:3857
    INTERPOLATION_TYPE_NAME = Nearest Neighbor
    RASTER_CELL_SIZE = Preserve Cells
    RASTER_TOLERANCE = 0.0
    REPROJECTED -> AttributeKeeper
AttributeKeeper
    CREATE_BULK_MODE_FEATURES = NO
    KEEP_ATTRS = g_elevatio,g_latitude,g_longitud,g_type
    -> PointOnAreaOverlayer_2 [POINT]
uniteevaluationfonciere (reader SHAPEFILE_5)
    attributes: ID_UEV varchar(80), CIVIQUE_DE varchar(80), CIVIQUE_FI varchar(80), NOM_RUE varchar(80), SUITE_DEBU varchar(80), MUNICIPALI varchar(80), ETAGE_HORS number(18,0), NOMBRE_LOG number(18,0), ANNEE_CONS number(18,0), CODE_UTILI varchar(80), LETTRE_DEB varchar(80), LETTRE_FIN varchar(80), LIBELLE_UT varchar(156), CATEGORIE_ varchar(80), MATRICULE8 varchar(80), SUPERFICIE number(18,0), SUPERFIC_1 number(18,0), NO_ARROND_ varchar(80)
    -> Reprojector_5
Reprojector_5
    DEST = EPSG:3857
    INTERPOLATION_TYPE_NAME = Nearest Neighbor
    RASTER_CELL_SIZE = Preserve Cells
    RASTER_TOLERANCE = 0.0
    REPROJECTED -> AttributeManager
AttributeManager
    ATTR_TABLE:
      REMOVE ID_UEV
      REMOVE CIVIQUE_DE
      REMOVE CIVIQUE_FI
      REMOVE NOM_RUE
      REMOVE SUITE_DEBU
      REMOVE MUNICIPALI
      RENAME_SET_VALUE ETAGE_HORS > etage_hors
      RENAME_SET_VALUE NOMBRE_LOG > nombre_log
      RENAME_SET_VALUE ANNEE_CONS > annee_construction
      REMOVE CODE_UTILI
      REMOVE LETTRE_DEB
      REMOVE LETTRE_FIN
      RENAME_SET_VALUE LIBELLE_UT > utilisation
      REMOVE CATEGORIE_
      REMOVE MATRICULE8
      REMOVE SUPERFICIE
      REMOVE SUPERFIC_1
      RENAME_SET_VALUE NO_ARROND_ > no_arrondissement
    -> PointOnAreaOverlayer_2 [AREA]
Note: Jointure spatiale afin d'attribuer les valeurs "z" aux polygones de bâtiments. / - À noter que les points ne couvrent pas tous les polygones alors plusieurs bâtiments n'auront pas d'élévation
PointOnAreaOverlayer_2
    ATTR_ACCUM_MODE = Merge Incoming
    ATTR_CONFLICT_RES = Use Original
    DEAGGREGATE_INPUT = Yes
    OV_ATTR = _overlaps
    POLYS_FIRST = NO
    AREA -> PointOnAreaOverlayer_3 [AREA]
    <REJECTED> -> Logger
Logger
    LOG_FEATURE = LOG_ONLY
    MAXCOORDS = 20
    MAXFEATS = 20
    MESSAGE = Feature is:
    SEVERITY = INFO

Bookmark: Attribution couleurs Raster aux bâtiments
PointOnAreaOverlayer_3
    ATTR_ACCUM_MODE = Merge Incoming
    ATTR_CONFLICT_RES = Use Original
    DEAGGREGATE_INPUT = Yes
    OV_ATTR = _overlaps
    POLYS_FIRST = NO
    AREA -> AttributeKeeper_2
    <REJECTED> -> Logger_19
Note: Nettoyage
AttributeKeeper_2
    CREATE_BULK_MODE_FEATURES = NO
    KEEP_ATTRS = annee_construction,color_rgb,etage_hors,fme_fill_color,g_elevatio,g_latitude,g_longitud,g_type,no_arrondissement,utilisation
    -> PointOnAreaOverlayer_4 [AREA]
Logger_19
    LOG_FEATURE = LOG_ONLY
    MAXCOORDS = 20
    MAXFEATS = 20
    MESSAGE = Feature is:
    SEVERITY = INFO

Bookmark: Simplification et combinaison de quatre nuages de points - Secteur limites Montréal-Nord/Ahuntsic
LAS (reader LAS_1)
    -> PointCloudThinner
PointCloudThinner
    INTERVAL = 30
    THINNED -> PointCloudCombiner
    <REJECTED> -> Logger_10
Logger_10
    LOG_FEATURE = LOG_ONLY
    MAXCOORDS = 20
    MAXFEATS = 20
    MESSAGE = Feature is:
    SEVERITY = INFO
LAS (reader LAS_4)
    -> PointCloudThinner_4
Note: Simplification à une intervalle de 30 pour les deux nuages de points.
PointCloudThinner_4
    INTERVAL = 30
    THINNED -> PointCloudCombiner
    <REJECTED> -> Logger_6
Note: Combinaison des nuages de points
PointCloudCombiner
    ACCUM_ATTRS_NAME = Yes
    EXTRACT_RASTER_NODATA_NAME = No
    SPACING = 1.0
    -> EsriReprojector
    <REJECTED> -> Logger_11
EsriReprojector
    DEST = ESRIWKT|WGS_1984_Web_Mercator_Auxiliary_Sphere|PROJCS["WGS_1984_Web_Mercator_Auxiliary_Sphere",GEOGCS["GCS_WGS_1984",DATUM["D_WGS_1984",SPHEROID["WGS_1984",6378137.0,298.257223563]],PRIMEM["Greenwich",0.0],UNIT["Degree",0.0174532925199433]],PROJECTION["Mercator_Auxiliary_Sphere"],PARAMETER["False_Easting",0.0],PARAMETER["False_Northing",0.0],PARAMETER["Central_Meridian",0.0],PARAMETER["Standard_Parallel_1",0.0],PARAMETER["Auxiliary_Sphere_Type",0.0],UNIT["Meter",1.0]]
    GEOTRANSFORMATION_NAME = NAD_1983_CSRS_To_WGS_1984
    INTERPOLATION_TYPE_NAME = Nearest Neighbor
    RASTER_CELL_SIZE = Preserve Cells
    RASTER_TOLERANCE = 0.0
    SOURCE = ESRIWKT|NAD_1983_CSRS_MTM_8|PROJCS["NAD_1983_CSRS_MTM_8",GEOGCS["GCS_North_American_1983_CSRS",DATUM["D_North_American_1983_CSRS",SPHEROID["GRS_1980",6378137.0,298.257222101]],PRIMEM["Greenwich",0.0],UNIT["Degree",0.0174532925199433]],PROJECTION["Transverse_Mercator"],PARAMETER["False_Easting",304800.0],PARAMETER["False_Northing",0.0],PARAMETER["Central_Meridian",-73.5],PARAMETER["Scale_Factor",0.9999],PARAMETER["Latitude_Of_Origin",0.0],UNIT["Meter",1.0]]
    REPROJECTED -> PointCloudThinner_5
Note: Deuxième simplification à une intervalle de 5
PointCloudThinner_5
    INTERVAL = 5
    THINNED -> PointCloudPropertyExtractor
    <REJECTED> -> Logger_12
Note: Extraction des attributs et valeurs des nuages de points
PointCloudPropertyExtractor
    CALCULATE_EXTENTS_DISPLAY = No
    POINT_COMPONENTS = x EXISTENCE PROPERTIES MINMAX y EXISTENCE PROPERTIES MINMAX z EXISTENCE PROPERTIES MINMAX
    -> PointCloudToPointCoercer
    <REJECTED> -> Logger_13
Note: Conversion des nuages de points en vecteurs (points)
PointCloudToPointCoercer
    ACCUM_ATTRS_NAME = Yes
    CONVERT_TO_DISPLAY = Individual Points
    PART_NUMBER_ATTR_NAME = _part_number
    POINT_COMPONENTS = normal_z color_red color_green color_blue
    POINT_COMPONENTS_PRESERVE_DISPLAY = Attributes
    COERCED -> PointOnAreaOverlayer_4 [POINT]
    <REJECTED> -> Logger_15
Logger_15
    LOG_FEATURE = LOG_ONLY
    MAXCOORDS = 20
    MAXFEATS = 20
    MESSAGE = Feature is:
    SEVERITY = INFO
Logger_13
    LOG_FEATURE = LOG_ONLY
    MAXCOORDS = 20
    MAXFEATS = 20
    SEVERITY = INFO
Logger_12
    LOG_FEATURE = LOG_ONLY
    MAXCOORDS = 20
    MAXFEATS = 20
    MESSAGE = Feature is:
    SEVERITY = INFO
Logger_11
    LOG_FEATURE = LOG_ONLY
    MAXCOORDS = 20
    MAXFEATS = 20
    MESSAGE = Feature is:
    SEVERITY = INFO
Logger_6
    LOG_FEATURE = LOG_ONLY
    MAXCOORDS = 20
    MAXFEATS = 20
    MESSAGE = Feature is:
    SEVERITY = INFO

Bookmark: Attribution des valeurs "z" aux bâtiments qui intersectent les points LiDAR
Note: Jointure spatiale pour compléter les valeurs "z" à une zone d'intérêt (limite entre arrondissements Ahuntsic et Montréal-Nord)
PointOnAreaOverlayer_4
    CANDIDATE_LIST_ATTRS_TO_INCLUDE_MODE = All Attributes
    CANDIDATE_LIST_NAME = z_accumulation
    DEAGGREGATE_INPUT = Yes
    OV_ATTR = _overlaps
    POLYS_FIRST = YES
    AREA -> ListSummer
    <REJECTED> -> Logger_16
Note: Calcul des sommes des élévations par polygone
ListSummer
    RESULT = _sum
    SRC_LIST = z_accumulation{}._z
    -> AttributeManager_6
Note: Nettoyage et calcul de la moyenne des valeurs "z"
AttributeManager_6
    ATTR_TABLE:
      REMOVE z_accumulation{}.fme_basename
      REMOVE z_accumulation{}._x
      REMOVE z_accumulation{}._x_scale
      REMOVE z_accumulation{}._x_offset
      REMOVE z_accumulation{}._x_encoding
      REMOVE z_accumulation{}._x_type
      REMOVE z_accumulation{}._x_min
      REMOVE z_accumulation{}._x_max
      REMOVE z_accumulation{}._y
      REMOVE z_accumulation{}._y_scale
      REMOVE z_accumulation{}._y_offset
      REMOVE z_accumulation{}._y_encoding
      REMOVE z_accumulation{}._y_type
      REMOVE z_accumulation{}._y_min
      REMOVE z_accumulation{}._y_max
      REMOVE z_accumulation{}._z
      REMOVE z_accumulation{}._z_scale
      REMOVE z_accumulation{}._z_offset
      REMOVE z_accumulation{}._z_encoding
      REMOVE z_accumulation{}._z_type
      REMOVE z_accumulation{}._z_min
      REMOVE z_accumulation{}._z_max
      REMOVE z_accumulation{}._num_points
      REMOVE z_accumulation{}.normal_z
      REMOVE z_accumulation{}.color_red
      REMOVE z_accumulation{}.color_green
      REMOVE z_accumulation{}.color_blue
      REMOVE z_accumulation{}._part_number
      SET_TO z = @Evaluate(@round(@Value(_sum)/@Value(_overlaps),4))
    USER_EXPOSED_ATTRIBUTES = z
    -> batiments_3D_RasterColor (writer POSTGIS_2)
Logger_16
    LOG_FEATURE = LOG_ONLY
    MAXCOORDS = 20
    MAXFEATS = 20
    MESSAGE = Feature is:
    SEVERITY = INFO

FME custom transformer ColorConverter
Converts color values between different formats (FME
 RGB
 Web RGB and CMYK)
Input:
1 attribute containing a color triplet in either FME, RGB, Web RGB or CMYK format, comma-separated
Output:
Attributes _output_color (full color triplet in the required format), _output_red, output_green and _output_blue
Supported color models:
FME color, RGB values in range 0..1
RGB values in range 0..255
Web RGB values, a hexadecimal string of 6 characters containing an RGB triplet with each value in the range 00..FF
CMYK values in range 0..1 and 0..100
Note that due to rounding errors the resulting colors might be a bit off. Especially any conversions between the RGB and CMYK color spaces might yield results that differ from other applications (since the RGB and CMYK color spaces are slightly different)

Parameters:
- InputAttribute = fme_fill_color   # " " Input color attribute
- InputModel = FME   # RGB"%"CMYK (0..1)"%"CMYK (0..100)" Input color model
- OutputModel = FME   # RGB"%"CMYK (0..1)"%"CMYK (0..100)" Output color model

Input (input)
    -> TestFilter
Note: Select input color model
TestFilter
    DEFAULT_VALUE = <UNFILTERED>
    TEST_LIST = BOOL_OP,OR,COMPOSITE_TEST,<Unused>,TEST_CLAUSE,"TEST $(InputModel) = FME",FME,BOOL_OP,OR,COMPOSITE_TEST,<Unused>,TEST_CLAUSE,"TEST $(InputModel) = RGB",RGB,BOOL_OP,OR,COMPOSITE_TEST,<Unused>,TEST_CLAUSE,"TEST $(InputModel) = Web RGB",Web RGB,BOOL_OP,OR,COMPOSITE_TEST,<Unused>,TEST_CLAUSE,"TEST $(InputModel) = CMYK (0..100)",CMYK (0..100),BOOL_OP,OR,COMPOSITE_TEST,<Unused>,TEST_CLAUSE,"TEST $(InputModel) = CMYK (0..1)",CMYK (0..1)
    FME -> AttributeSplitter
    RGB -> AttributeSplitter_2
    Web RGB -> StringReplacer
    CMYK (0..100) -> AttributeSplitter_5
    CMYK (0..1) -> AttributeSplitter_4
Note: Select output color model
TestFilter_2
    DEFAULT_VALUE = <UNFILTERED>
    TEST_LIST = BOOL_OP,OR,COMPOSITE_TEST,<Unused>,TEST_CLAUSE,"TEST $(OutputModel) = FME",FME,BOOL_OP,OR,COMPOSITE_TEST,<Unused>,TEST_CLAUSE,"TEST $(OutputModel) = RGB",RGB,BOOL_OP,OR,COMPOSITE_TEST,<Unused>,TEST_CLAUSE,"TEST $(OutputModel) = Web RGB",Web RGB,BOOL_OP,OR,COMPOSITE_TEST,<Unused>,TEST_CLAUSE,"TEST $(OutputModel) = CMYK (0..1)",CMYK (0..1),BOOL_OP,OR,COMPOSITE_TEST,<Unused>,TEST_CLAUSE,"TEST $(OutputModel) = CMYK (0..100)",CMYK (0..100)
    FME -> AttributeManager_5
    RGB -> AttributeManager_2
    Web RGB -> AttributeManager_7
    CMYK (0..1) -> AttributeManager_10
    CMYK (0..100) -> AttributeManager_11
Output (output)

Bookmark: FME color triplet
AttributeSplitter
    ATTR_NAME = $(InputAttribute)
    DELIMITER = ,
    DROP_EMPTY_PARTS = No
    LIST_NAME = _list
    TRIM_OPTION = Both
    -> AttributeManager
AttributeManager
    ATTR_TABLE:
      SET_TO _input_red = @Value(_list{0})
      SET_TO _input_green = @Value(_list{1})
      SET_TO _input_blue = @Value(_list{2})
    -> TestFilter_2

Bookmark: RGB color triplet
AttributeSplitter_2
    ATTR_NAME = $(InputAttribute)
    DELIMITER = ,
    DROP_EMPTY_PARTS = No
    LIST_NAME = _list
    TRIM_OPTION = Both
    -> AttributeManager_3
AttributeManager_3
    ATTR_TABLE:
      SET_TO _input_red = @Evaluate(@Value(_list{0})/255)
      SET_TO _input_green = @Evaluate(@Value(_list{1})/255)
      SET_TO _input_blue = @Evaluate(@Value(_list{2})/255)
    -> TestFilter_2

Bookmark: Web RGB (hexadecimal)
StringReplacer
    CASE = NO
    FIND_TEXT = ^#
    NO_MATCH = _FME_NO_OP_
    REGEXP = YES
    SRC_ATTRS = $(InputAttribute)
    -> AttributeSplitter_3
AttributeSplitter_3
    ATTR_NAME = $(InputAttribute)
    DELIMITER = 2s2s2s
    DROP_EMPTY_PARTS = No
    LIST_NAME = _list
    TRIM_OPTION = Both
    -> BaseConverter
BaseConverter
    DBASE = 10
    OBASE = 16
    SRC = _list{0}
    VAL_ATTR = _input_red
    WIDTH = 3
    -> BaseConverter_2
BaseConverter_2
    DBASE = 10
    OBASE = 16
    SRC = _list{1}
    VAL_ATTR = _input_green
    WIDTH = 3
    -> BaseConverter_3
BaseConverter_3
    DBASE = 10
    OBASE = 16
    SRC = _list{2}
    VAL_ATTR = _input_blue
    WIDTH = 3
    -> AttributeManager_4
AttributeManager_4
    ATTR_TABLE:
      SET_TO _input_red = @Evaluate(@Value(_input_red)/255)
      SET_TO _input_green = @Evaluate(@Value(_input_green)/255)
      SET_TO _input_blue = @Evaluate(@Value(_input_blue)/255)
    -> TestFilter_2

Bookmark: CMYK
AttributeSplitter_5
    ATTR_NAME = $(InputAttribute)
    DELIMITER = ,
    DROP_EMPTY_PARTS = No
    LIST_NAME = _list
    TRIM_OPTION = Both
    -> AttributeManager_9
AttributeManager_9
    ATTR_TABLE:
      SET_TO _input_red = @Evaluate((1-(@Value(_list{0})/100))*(1-(@Value(_list{3})/100)))
      SET_TO _input_green = @Evaluate((1-(@Value(_list{1})/100))*(1-(@Value(_list{3})/100)))
      SET_TO _input_blue = @Evaluate((1-(@Value(_list{2})/100))*(1-(@Value(_list{3})/100)))
    -> TestFilter_2
AttributeSplitter_4
    ATTR_NAME = $(InputAttribute)
    DELIMITER = ,
    DROP_EMPTY_PARTS = No
    LIST_NAME = _list
    TRIM_OPTION = Both
    -> AttributeManager_8
AttributeManager_8
    ATTR_TABLE:
      SET_TO _input_red = @Evaluate((1-@Value(_list{0}))*(1-@Value(_list{3})))
      SET_TO _input_green = @Evaluate((1-@Value(_list{1}))*(1-@Value(_list{3})))
      SET_TO _input_blue = @Evaluate((1-@Value(_list{2}))*(1-@Value(_list{3})))
    -> TestFilter_2

Bookmark: FME color triplet
AttributeManager_5
    ATTR_TABLE:
      RENAME_SET_VALUE _input_red > _output_red
      RENAME_SET_VALUE _input_green > _output_green
      RENAME_SET_VALUE _input_blue > _output_blue
      SET_TO _output_color = @Value(_output_red),@Value(_output_green),@Value(_output_blue)
    -> Output (output)

Bookmark: RGB color triplet
AttributeManager_2
    ATTR_TABLE:
      SET_TO _output_red = @Evaluate(@int(@Value(_input_red)*255))
      SET_TO _output_green = @Evaluate(@int(@Value(_input_green)*255))
      SET_TO _output_blue = @Evaluate(@int(@Value(_input_blue)*255))
      SET_TO _output_color = @Value(_output_red),@Value(_output_green),@Value(_output_blue)
    -> Output (output)

Bookmark: Web RGB (hexadecimal
AttributeManager_7
    ATTR_TABLE:
      SET_TO _input_red = @Evaluate(int(@Value(_input_red)*255))
      SET_TO _input_green = @Evaluate(int(@Value(_input_green)*255))
      SET_TO _input_blue = @Evaluate(int(@Value(_input_blue)*255))
    -> BaseConverter_4
    -> AttributeManager_7_Output
BaseConverter_4
    DBASE = 16
    OBASE = 10
    SRC = _input_red
    VAL_ATTR = _output_red
    WIDTH = 2
    -> BaseConverter_5
BaseConverter_5
    DBASE = 16
    OBASE = 10
    SRC = _input_green
    VAL_ATTR = _output_green
    WIDTH = 2
    -> BaseConverter_6
BaseConverter_6
    DBASE = 16
    OBASE = 10
    SRC = _input_blue
    VAL_ATTR = _output_blue
    WIDTH = 2
    -> AttributeManager_6
AttributeManager_6
    ATTR_TABLE = SET_TO _output_color = #@Value(_output_red)@Value(_output_green)@Value(_output_blue)
    -> Output (output)
AttributeManager_7_Output: Inspector

Bookmark: CMYK
AttributeManager_10
    ATTR_TABLE:
      SET_TO _output_key = @Evaluate(1-@max(@Value(_input_red),@Value(_input_green),@Value(_input_blue)))
      SET_TO _output_cyan = @Evaluate((1-@Value(_input_red)-@Value(_output_key))/(1-@Value(_output_key)))
      SET_TO _output_magenta = @Evaluate((1-@Value(_input_green)-@Value(_output_key))/(1-@Value(_output_key)))
      SET_TO _output_yellow = @Evaluate((1-@Value(_input_blue)-@Value(_output_key))/(1-@Value(_output_key)))
    -> AttributeRounder
AttributeManager_11
    ATTR_TABLE:
      SET_TO _output_key = @Evaluate((1-@max(@Value(_input_red),@Value(_input_green),@Value(_input_blue)))*100)
      SET_TO _output_cyan = @Evaluate(((1-@Value(_input_red)-@Value(_output_key))/(1-@Value(_output_key)))*100)
      SET_TO _output_magenta = @Evaluate(((1-@Value(_input_green)-@Value(_output_key))/(1-@Value(_output_key)))*100)
      SET_TO _output_yellow = @Evaluate(((1-@Value(_input_blue)-@Value(_output_key))/(1-@Value(_output_key)))*100)
    -> AttributeRounder
AttributeRounder
    PLACES = 2
    ROUND_TYPE = Nearest
    SRC_ATTRS = _output_cyan _output_key _output_yellow _output_magenta
    -> AttributeManager_12
AttributeManager_12
    ATTR_TABLE = SET_TO _output_color = @Value(_output_cyan),@Value(_output_magenta),@Value(_output_yellow),@Value(_output_key)
    -> Output (output)
