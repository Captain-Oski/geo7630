FME workspace TP1_Popa_Diana.fmw

Parameters:
- SourceDataset_SHAPEFILE = D:\DESS SIG\GEO7630 - Intégration et visualisation des données géographiques\Travaux\TP1\TP1 (visualisation données)\dmti_building_2021_p_point.shp   # Source Esri Shapefile(s)
- SourceDataset_SHAPEFILE_11 = https://data.montreal.ca/dataset/2fc8a2b9-1556-410e-a118-c46e97e9f19e/resource/c08b5a11-549f-409d-9d2a-04eb3a10b66a/download/interventions-sim.zip   # Source Esri Shapefile(s)
- SourceDataset_SHAPEFILE_9 = https://data.montreal.ca/dataset/5829b5b0-ea6f-476f-be94-bc2b8797769a/resource/1171793b-3c41-4dd5-ab99-7bd294c0c9f0/download/actes-criminels.zip   # Source Esri Shapefile(s)
- SourceDataset_SHAPEFILE_8 = https://data.montreal.ca/dataset/49af1f40-6a69-494f-8fa3-b84b532a7dd6/resource/7157e8e8-8d01-4d3f-b99b-28a79db013ce/download/territoires-administratifs-casernes.zip   # Source Esri Shapefile(s)
- SourceDataset_SHAPEFILE_7 = https://data.montreal.ca/dataset/4ad6baea-4d2c-460f-a8bf-5d000db498f7/resource/43c2cccf-a439-429b-a3c8-5d4ebce53e1b/download/uniteevaluationfonciere.zip   # Source Esri Shapefile(s)

Readers:
- SHAPEFILE_1: SHAPEFILE from $(SourceDataset_SHAPEFILE)
- SHAPEFILE_2: SHAPEFILE from $(SourceDataset_SHAPEFILE_11)
- SHAPEFILE_3: SHAPEFILE from $(SourceDataset_SHAPEFILE_9)
- SHAPEFILE_4: SHAPEFILE from $(SourceDataset_SHAPEFILE_8)
- SHAPEFILE_5: SHAPEFILE from $(SourceDataset_SHAPEFILE_7)

Bookmark: Bâtiments (Geoindex), Unités d'évaluation foncière - Reprojection (3857), jointure spatiale, indexation hexagonale (H3)
dmti_building_2021_p_point (reader SHAPEFILE_1)
    attributes: g_objectid varchar(50), g_uid varchar(36), g_name varchar(70), g_address varchar(45), g_municipa varchar(60), g_prov varchar(2), g_post_cod varchar(7), g_phone varchar(15), g_fax varchar(11), g_toll_fre varchar(15), g_type varchar(15), g_longitud varchar(50), g_latitude varchar(50), g_elevatio varchar(50), g_accuracy varchar(50), g_acq_tech varchar(50), g_dat_acqu varchar(50), g_dat_char varchar(50)
    -> Reprojector
Reprojector
    DEST = EPSG:3857
    INTERPOLATION_TYPE_NAME = Nearest Neighbor
    RASTER_CELL_SIZE = Preserve Cells
    RASTER_TOLERANCE = 0.0
    REPROJECTED -> AttributeKeeper
AttributeKeeper
    CREATE_BULK_MODE_FEATURES = NO
    KEEP_ATTRS = g_elevatio,g_latitude,g_longitud,g_type,g_address,g_post_cod,g_name,g_objectid,g_uid
    -> PointOnAreaOverlayer_2 [POINT]
uniteevaluationfonciere (reader SHAPEFILE_5)
    attributes: ID_UEV varchar(80), CIVIQUE_DE varchar(80), CIVIQUE_FI varchar(80), NOM_RUE varchar(80), SUITE_DEBU varchar(80), MUNICIPALI varchar(80), ETAGE_HORS number(18,0), NOMBRE_LOG number(18,0), ANNEE_CONS number(18,0), CODE_UTILI varchar(80), LETTRE_DEB varchar(80), LETTRE_FIN varchar(80), LIBELLE_UT varchar(156), CATEGORIE_ varchar(80), MATRICULE8 varchar(80), SUPERFICIE number(18,0), SUPERFIC_1 number(18,0), NO_ARROND_ varchar(80)
    -> Reprojector_5
Reprojector_5
    DEST = EPSG:3857
    INTERPOLATION_TYPE_NAME = Nearest Neighbor
    RASTER_CELL_SIZE = Preserve Cells
    RASTER_TOLERANCE = 0.0
    REPROJECTED -> AttributeManager
AttributeManager
    ATTR_TABLE:
      RENAME_SET_VALUE ID_UEV > id_uev
      RENAME_SET_VALUE CIVIQUE_DE > civique_de
      RENAME_SET_VALUE CIVIQUE_FI > civique_fi
      RENAME_SET_VALUE NOM_RUE > nom_rue
      REMOVE SUITE_DEBU
      REMOVE MUNICIPALI
      RENAME_SET_VALUE ETAGE_HORS > etage_hors
      RENAME_SET_VALUE NOMBRE_LOG > logements
      RENAME_SET_VALUE ANNEE_CONS > annee_construction
      REMOVE CODE_UTILI
      REMOVE LETTRE_DEB
      REMOVE LETTRE_FIN
      RENAME_SET_VALUE LIBELLE_UT > libelle_ut
      RENAME_SET_VALUE CATEGORIE_ > categorie
      REMOVE MATRICULE8
      RENAME_SET_VALUE SUPERFICIE > superficie
      RENAME_SET_VALUE SUPERFIC_1 > superficie_1
      RENAME_SET_VALUE NO_ARROND_ > no_arrondissement
    -> PointOnAreaOverlayer_2 [AREA]
PointOnAreaOverlayer_2
    DEAGGREGATE_INPUT = Yes
    OV_ATTR = _overlaps
    POLYS_FIRST = No
    <REJECTED> -> Logger
Logger
    LOG_FEATURE = LOG_ONLY
    MAXCOORDS = 20
    MAXFEATS = 20
    MESSAGE = Feature is:
    SEVERITY = INFO

Bookmark: Actes criminels et interventions SIM - Reprojection (3857), reconfiguration des attributs, jointure des deux tables
actes-criminels (reader SHAPEFILE_3)
    attributes: CATEGORIE varchar(80), DATE varchar(80), QUART varchar(80), PDQ double, X double, Y double, LONGITUDE double, LATITUDE double
    -> Reprojector_3
Reprojector_3
    DEST = EPSG:3857
    INTERPOLATION_TYPE_NAME = Nearest Neighbor
    RASTER_CELL_SIZE = Preserve Cells
    RASTER_TOLERANCE = 0.0
    REPROJECTED -> Configuration_latitude
Configuration_latitude: SubstringExtractor
    END = 4
    RESULT_ATTR = Latitude
    SRC_STRING = @Value(LATITUDE)
    START = 0
    -> Configuration_longitude
Configuration_longitude: SubstringExtractor
    END = 5
    RESULT_ATTR = Longitude
    SRC_STRING = @Value(LONGITUDE)
    START = 0
    -> FeatureMerger [REQUESTOR]
interventions-sim (reader SHAPEFILE_2)
    attributes: INCIDENT_N number(18,0), CREATION_D varchar(80), INCIDENT_T varchar(80), DESCRIPTIO varchar(80), CASERNE number(18,0), NOM_VILLE varchar(80), NOM_ARROND varchar(80), DIVISION number(18,0), NOMBRE_UNI double, MTM8_X double, MTM8_Y double, LONGITUDE double, LATITUDE double
    -> Reprojector_4
Reprojector_4
    DEST = EPSG:3857
    INTERPOLATION_TYPE_NAME = Nearest Neighbor
    RASTER_CELL_SIZE = Preserve Cells
    RASTER_TOLERANCE = 0.0
    REPROJECTED -> Suppression_Heure
Note: Contrairement aux crimes, le champs comportant la date de l'événement incluait également l'heure. Afin de pouvoir le joindre au document "Actes criminels", j'ai conservé la date seulement. / - Nouveau champ : "Date"
Suppression_Heure: SubstringExtractor
    END = 9
    RESULT_ATTR = Date
    SRC_STRING = @Value(CREATION_D)
    START = 0
    -> Configuration_latitude_SIM
Configuration_latitude_SIM: SubstringExtractor
    END = 4
    RESULT_ATTR = Latitude_SIM
    SRC_STRING = @Value(LATITUDE)
    START = 0
    -> Configuration_longitude_SIM
Note: Reconfiguration de la précision des latitudes et longitudes à deux décimales. Considérant que la localisation des points est approximative afin de conserver la confidentialité des événements, il semblait logique que des points (crimes et interventions) à proximité ayant la même date soient considérés comme le même événement. Cette étape a été appliquée aux crimes et interventions SIM afin de les joindre.
Configuration_longitude_SIM: SubstringExtractor
    END = 5
    RESULT_ATTR = Longitude_SIM
    SRC_STRING = @Value(LONGITUDE)
    START = 0
    -> FeatureMerger [SUPPLIER]
Note: Jointure des deux tables en fonction des dates et coordonnées X,Y qui sont les mêmes.
FeatureMerger
    ATTR_ACCUM_MODE = Merge Supplier
    ATTR_CONFLICT_RES = Use Requestor
    IGNORE_NULLS = No
    JOIN_KEYS = @Value(DATE) @Value(Date) AUTO @Value(Latitude) @Value(Latitude_SIM) AUTO @Value(Longitude) @Value(Longitude_SIM) AUTO
    MERGE_TYPE = Attributes and Geometry
    PROCESS_DUPS = NO
    REJECT_NULL_MISSING_KEYS = No
    SUPPLIERS_FIRST = No
    MERGED -> AttributeManager_2
    <REJECTED> -> Logger_2
AttributeManager_2
    ATTR_TABLE:
      RENAME_SET_VALUE CATEGORIE > categorie
      RENAME_SET_VALUE DATE > date
      RENAME_SET_VALUE QUART > quart
      RENAME_SET_VALUE PDQ > pdq
      RENAME_SET_VALUE X > x
      RENAME_SET_VALUE Y > y
      RENAME_SET_VALUE LONGITUDE > longitude
      RENAME_SET_VALUE LATITUDE > latitude
      RENAME_SET_VALUE Latitude > latitude_ac
      RENAME_SET_VALUE Longitude > longitude_ac
      RENAME_SET_VALUE INCIDENT_N > incident_n
      RENAME_SET_VALUE CREATION_D > creation_d
      RENAME_SET_VALUE INCIDENT_T > incident_t
      RENAME_SET_VALUE DESCRIPTIO > description
      RENAME_SET_VALUE CASERNE > caserne
      REMOVE NOM_VILLE
      RENAME_SET_VALUE NOM_ARROND > nom_arrondissement
      RENAME_SET_VALUE DIVISION > division
      RENAME_SET_VALUE NOMBRE_UNI > nombre_uni
      RENAME_SET_VALUE MTM8_X > mtm8_x
      RENAME_SET_VALUE MTM8_Y > mtm8_y
      RENAME_SET_VALUE Date > date_reconfig
      RENAME_SET_VALUE Latitude_SIM > latitude_sim
      RENAME_SET_VALUE Longitude_SIM > longitude_sim
    -> PointOnAreaOverlayer [POINT]
Logger_2
    LOG_FEATURE = LOG_ONLY
    MAXCOORDS = 20
    MAXFEATS = 20
    MESSAGE = Feature is:
    SEVERITY = INFO

Bookmark: Tendances obtenues et les territoires des casernes - Jointure spatiale, Indexation hexagonale (H3)
Note: CONVERSION UTM À LAT/LONG???
territoires-administratifs-casernes (reader SHAPEFILE_4)
    attributes: NOM_CAS_AD varchar(80), NO_CAS_ADM long, OBJECTID long
    -> CoordinateExtractor
CoordinateExtractor
    IND = 0
    MODE = Specify Coordinate
    X_ATTR = _x
    Y_ATTR = _y
    -> VertexCreator
VertexCreator
    MEASURE_TYPE = Continuous
    MODE_NAME = Replace with Point
    XVAL = @Value(_x)
    YVAL = @Value(_y)
    -> H3HexagonalIndexer
H3HexagonalIndexer
    INDEX_OPERATION = Index
    -> Dissolver
    <REJECTED> -> Logger_4
Dissolver
    ACCUM_INPUT_ATTRS = Merge Incoming Attributes
    CLEANING_TOLERANCE = Automatic
    CONNECT_Z_MODE = First Wins
    DEAGGREGATE_INPUT = Yes
    GROUP_BY = _h3index
    AREA -> PointOnAreaOverlayer [AREA]
    <REJECTED> -> Logger_5
Note: Jointure spatiale du résultat (tendances entres crimes et interventions SIM) et les territoires administratifs des casernes.
PointOnAreaOverlayer
    DEAGGREGATE_INPUT = Yes
    OV_ATTR = _overlaps
    POLYS_FIRST = No
    <REJECTED> -> Logger_3
Logger_3
    LOG_FEATURE = LOG_ONLY
    MAXCOORDS = 20
    MAXFEATS = 20
    MESSAGE = Feature is:
    SEVERITY = INFO
Logger_5
    LOG_FEATURE = LOG_ONLY
    MAXCOORDS = 20
    MAXFEATS = 20
    MESSAGE = Feature is:
    SEVERITY = INFO
Logger_4
    LOG_FEATURE = LOG_ONLY
    MAXCOORDS = 20
    MAXFEATS = 20
    MESSAGE = Feature is:
    SEVERITY = INFO
