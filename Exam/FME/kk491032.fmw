FME workspace kk491032.fmw

Parameters:
- DestDataset_POSTGIS =
- SourceDataset_GEOJSON =
- SourceDataset_GEOJSON_3 =

Readers:
- GEOJSON_1: GEOJSON from $(SourceDataset_GEOJSON)
- GEOJSON_2: GEOJSON from $(SourceDataset_GEOJSON_3)

Writers:
- POSTGIS_1: POSTGIS to $(DestDataset_POSTGIS)

PointOnAreaOverlayer
    ATTR_ACCUM_MODE = Merge Incoming
    ATTR_CONFLICT_RES = Use Original
    DEAGGREGATE_INPUT = Yes
    OV_ATTR = Point_count
    POLYS_FIRST = NO
    POINT -> AttributeKeeper
    AREA -> AttributeKeeper
    <REJECTED> -> PointOnAreaOverlayer__Rejected_
AttributeKeeper
    CREATE_BULK_MODE_FEATURES = NO
    KEEP_ATTRS = _h3index,_overlaps,A_LOUER_CONTACT,A_LOUER_TELEPHONE,ACCES_MOBILITE_REDUITE,ADRESSE,ARRONDISSEMENT,CIVIQUE,CODE_POST,COORDX,COORDY,DATE_RECENSEMENT,DefaultAtt,ENFANT,ETAGE,ID,ID_USAGE1,ID_USAGE2,ID_USAGE3,LAT,LIEN_VOIE,LONG,MULTIOCCUPANT,MULTIUSAGE,NEQ,NOM_CENTRE,NOM_ETAB,NOM_VOIE,ORIENTATION,ORIGINE,QUARTIER,SCIAN,SDC_NOM,SECTEUR_PME,SITE_TRANSACTIONNEL,SITEWEB,SUFFIXE_NEQ,SUITE,T_COMMERCE,TYPE_VOIE,USAGE1,USAGE2,USAGE3,VACANT_A_LOUER
    -> LEVM27119705 (writer POSTGIS_1)
LEVM27119705 (writer POSTGIS_1)
    attributes: id text, origine text, t_commerce text, date_recensement text, civique text, type_voie text, lien_voie text, nom_voie text, orientation text, adresse text, suite text, code_post text, etage text, nom_centre text, nom_etab text, id_usage1 text, usage1 text, id_usage2 text, usage2 text, id_usage3 text, usage3 text, scian text, siteweb text, site_transactionnel text, acces_mobilite_reduite text, vacant_a_louer text, a_louer_contact text, a_louer_telephone text, arrondissement text, quartier text,
      sdc_nom text, secteur_pme text, enfant text, multiusage text, multioccupant text, neq text, suffixe_neq text, coordx text, coordy text, lat text, long text, defaultatt text, _h3index numeric(20,0)
PointOnAreaOverlayer__Rejected_: Logger
    LOG_FEATURE = LOG_ONLY
    MAXCOORDS = 20
    MAXFEATS = 20
    MESSAGE = Feature is:
    SEVERITY = INFO

Bookmark: Filtrage des commerces
OCcupation commerciale 2022 (reader GEOJSON_1)
    attributes: ID string, ORIGINE string, T_COMMERCE string, DATE_RECENSEMENT string, CIVIQUE string, TYPE_VOIE string, LIEN_VOIE string, NOM_VOIE string, ORIENTATION string, ADRESSE string, SUITE string, CODE_POST string, ETAGE string, NOM_CENTRE string, NOM_ETAB string, ID_USAGE1 string, USAGE1 string, ID_USAGE2 string, USAGE2 string, ID_USAGE3 string, USAGE3 string, SCIAN string, SITEWEB string, SITE_TRANSACTIONNEL string, ACCES_MOBILITE_REDUITE string, VACANT_A_LOUER string, A_LOUER_CONTACT string, A_LOUER_TELEPHONE string, ARRONDISSEMENT string, QUARTIER string,
      SDC_NOM string, SECTEUR_PME string, ENFANT string, MULTIUSAGE string, MULTIOCCUPANT string, NEQ string, SUFFIXE_NEQ string, COORDX string, COORDY string, LAT string, LONG string
    -> VertexCreator_2
VertexCreator_2
    MEASURE_TYPE = Continuous
    MODE_NAME = Replace with Point
    XVAL = @Value(LONG)
    YVAL = @Value(LAT)
    -> AttributeFilter
    <REJECTED> -> VertexCreator__Rejected_
AttributeFilter
    ATTR_NAME = USAGE1
    ATTR_VALUES = <Empty>,<Missing>,<Null>,<Unfiltered>,VACANT
    VACANT -> AttributeKeeper_2
AttributeKeeper_2
    CREATE_BULK_MODE_FEATURES = NO
    KEEP_ATTRS = A_LOUER_CONTACT,A_LOUER_TELEPHONE,ACCES_MOBILITE_REDUITE,ADRESSE,ARRONDISSEMENT,CIVIQUE,CODE_POST,COORDX,COORDY,DATE_RECENSEMENT,ENFANT,ETAGE,ID,ID_USAGE1,ID_USAGE2,ID_USAGE3,LAT,LIEN_VOIE,LONG,MULTIOCCUPANT,MULTIUSAGE,NEQ,NOM_CENTRE,NOM_ETAB,NOM_VOIE,ORIENTATION,ORIGINE,QUARTIER,SCIAN,SDC_NOM,SECTEUR_PME,SITE_TRANSACTIONNEL,SITEWEB,SUFFIXE_NEQ,SUITE,T_COMMERCE,TYPE_VOIE,USAGE1,USAGE2,USAGE3,VACANT_A_LOUER
    -> PointOnAreaOverlayer [POINT]
VertexCreator__Rejected_: Logger
    LOG_FEATURE = LOG_ONLY
    MAXCOORDS = 20
    MAXFEATS = 20
    MESSAGE = Feature is:
    SEVERITY = INFO

Bookmark: Génération des Hexagones
limites-terrestres (reader GEOJSON_2)
    attributes: DefaultAtt string
    -> H3HexagonalIndexer
H3HexagonalIndexer
    INDEX_OPERATION = Filling Indexes
    -> Dissolver
    <REJECTED> -> H3HexagonalIndexer__Rejected_
Dissolver
    ACCUM_INPUT_ATTRS = Merge Incoming Attributes
    CLEANING_TOLERANCE = Automatic
    CONNECT_Z_MODE = First Wins
    DEAGGREGATE_INPUT = Yes
    GROUP_BY = _h3index
    AREA -> PointOnAreaOverlayer [AREA]
H3HexagonalIndexer__Rejected_: Logger
    LOG_FEATURE = LOG_ONLY
    MAXCOORDS = 20
    MAXFEATS = 20
    MESSAGE = Feature is:
    SEVERITY = INFO
